;;; =========================================================================
;;; AutoLISP Batch Runner: Instanciar TODOS los 29 tamaños de UBOLT_STANDARD
;;; Arrastra este archivo al dibujo de AutoCAD o teclea: TESTALLSIZES
;;; =========================================================================

(defun c:TESTALLSIZES ( / ent xOffset spacing nd od)
  (vl-load-com)
  (princ "\n[+] Cargando PnP3dACPAdapter...")
  (arxload "PnP3dACPAdapter")
  (princ "\n[+] Registrando CustomScripts...")
  (vl-cmdf "PLANTREGISTERCUSTOMSCRIPTS")
  
  (setq xOffset 0.0)
  (princ "\n[+] Insertando 29 tamaños en fila ordenada...")

  ;; Talla ND 0.25" (OD=0.54")
  (testacpscript "UBOLT_STANDARD" "OD" "0.540000" "A" "0.250000" "B" "0.629900" "C" "0.866100" "D" "1.102400" "E" "0.984300" "F" "0.826800")
  (setq ent (entlast))
  (if ent (vl-cmdf "_.move" ent "" '(0 0 0) (list xOffset 0 0)))
  (setq xOffset (+ xOffset 8.0))

  ;; Talla ND 0.375" (OD=0.675")
  (testacpscript "UBOLT_STANDARD" "OD" "0.675000" "A" "0.250000" "B" "0.748000" "C" "0.984300" "D" "2.598400" "E" "2.244100" "F" "2.244100")
  (setq ent (entlast))
  (if ent (vl-cmdf "_.move" ent "" '(0 0 0) (list xOffset 0 0)))
  (setq xOffset (+ xOffset 8.0))

  ;; Talla ND 0.5" (OD=0.84")
  (testacpscript "UBOLT_STANDARD" "OD" "0.840000" "A" "0.250000" "B" "0.944900" "C" "1.181100" "D" "2.637800" "E" "2.244100" "F" "2.204700")
  (setq ent (entlast))
  (if ent (vl-cmdf "_.move" ent "" '(0 0 0) (list xOffset 0 0)))
  (setq xOffset (+ xOffset 8.0))

  ;; Talla ND 0.75" (OD=1.05")
  (testacpscript "UBOLT_STANDARD" "OD" "1.050000" "A" "0.250000" "B" "1.141700" "C" "1.378000" "D" "2.677200" "E" "2.244100" "F" "2.165400")
  (setq ent (entlast))
  (if ent (vl-cmdf "_.move" ent "" '(0 0 0) (list xOffset 0 0)))
  (setq xOffset (+ xOffset 8.0))

  ;; Talla ND 1.0" (OD=1.315")
  (testacpscript "UBOLT_STANDARD" "OD" "1.315000" "A" "0.250000" "B" "1.417300" "C" "1.653500" "D" "2.677200" "E" "2.244100" "F" "2.086600")
  (setq ent (entlast))
  (if ent (vl-cmdf "_.move" ent "" '(0 0 0) (list xOffset 0 0)))
  (setq xOffset (+ xOffset 8.0))

  ;; Talla ND 1.25" (OD=1.66")
  (testacpscript "UBOLT_STANDARD" "OD" "1.660000" "A" "0.375000" "B" "1.771700" "C" "2.126000" "D" "2.677200" "E" "2.244100" "F" "1.850400")
  (setq ent (entlast))
  (if ent (vl-cmdf "_.move" ent "" '(0 0 0) (list xOffset 0 0)))
  (setq xOffset (+ xOffset 8.0))

  ;; Talla ND 1.5" (OD=1.9")
  (testacpscript "UBOLT_STANDARD" "OD" "1.900000" "A" "0.375000" "B" "2.007900" "C" "2.362200" "D" "2.874000" "E" "2.244100" "F" "1.929100")
  (setq ent (entlast))
  (if ent (vl-cmdf "_.move" ent "" '(0 0 0) (list xOffset 0 0)))
  (setq xOffset (+ xOffset 8.0))

  ;; Talla ND 2.0" (OD=2.375")
  (testacpscript "UBOLT_STANDARD" "OD" "2.375000" "A" "0.375000" "B" "2.519700" "C" "2.874000" "D" "3.385800" "E" "2.244100" "F" "2.204700")
  (setq ent (entlast))
  (if ent (vl-cmdf "_.move" ent "" '(0 0 0) (list xOffset 0 0)))
  (setq xOffset (+ xOffset 8.28))

  ;; Talla ND 2.5" (OD=2.875")
  (testacpscript "UBOLT_STANDARD" "OD" "2.875000" "A" "0.500000" "B" "3.110200" "C" "3.622000" "D" "3.700800" "E" "2.992100" "F" "2.204700")
  (setq ent (entlast))
  (if ent (vl-cmdf "_.move" ent "" '(0 0 0) (list xOffset 0 0)))
  (setq xOffset (+ xOffset 9.18))

  ;; Talla ND 3.0" (OD=3.5")
  (testacpscript "UBOLT_STANDARD" "OD" "3.500000" "A" "0.500000" "B" "3.622000" "C" "4.133900" "D" "3.976400" "E" "2.992100" "F" "2.244100")
  (setq ent (entlast))
  (if ent (vl-cmdf "_.move" ent "" '(0 0 0) (list xOffset 0 0)))
  (setq xOffset (+ xOffset 10.3))

  ;; Talla ND 3.5" (OD=4.0")
  (testacpscript "UBOLT_STANDARD" "OD" "4.000000" "A" "0.500000" "B" "4.173200" "C" "4.685000" "D" "4.212600" "E" "2.992100" "F" "2.204700")
  (setq ent (entlast))
  (if ent (vl-cmdf "_.move" ent "" '(0 0 0) (list xOffset 0 0)))
  (setq xOffset (+ xOffset 11.2))

  ;; Talla ND 4.0" (OD=4.5")
  (testacpscript "UBOLT_STANDARD" "OD" "4.500000" "A" "0.500000" "B" "4.645700" "C" "5.157500" "D" "4.488200" "E" "2.992100" "F" "2.244100")
  (setq ent (entlast))
  (if ent (vl-cmdf "_.move" ent "" '(0 0 0) (list xOffset 0 0)))
  (setq xOffset (+ xOffset 12.1))

  ;; Talla ND 5.0" (OD=5.563")
  (testacpscript "UBOLT_STANDARD" "OD" "5.563000" "A" "0.500000" "B" "5.669300" "C" "6.181100" "D" "4.921300" "E" "2.992100" "F" "2.126000")
  (setq ent (entlast))
  (if ent (vl-cmdf "_.move" ent "" '(0 0 0) (list xOffset 0 0)))
  (setq xOffset (+ xOffset 14.01))

  ;; Talla ND 6.0" (OD=6.625")
  (testacpscript "UBOLT_STANDARD" "OD" "6.625000" "A" "0.625000" "B" "6.811000" "C" "7.440900" "D" "6.102400" "E" "3.740200" "F" "2.795300")
  (setq ent (entlast))
  (if ent (vl-cmdf "_.move" ent "" '(0 0 0) (list xOffset 0 0)))
  (setq xOffset (+ xOffset 15.93))

  ;; Talla ND 8.0" (OD=8.625")
  (testacpscript "UBOLT_STANDARD" "OD" "8.625000" "A" "0.625000" "B" "8.818900" "C" "9.448800" "D" "7.086600" "E" "3.740200" "F" "2.755900")
  (setq ent (entlast))
  (if ent (vl-cmdf "_.move" ent "" '(0 0 0) (list xOffset 0 0)))
  (setq xOffset (+ xOffset 19.52))

  ;; Talla ND 10.0" (OD=10.75")
  (testacpscript "UBOLT_STANDARD" "OD" "10.750000" "A" "0.750000" "B" "10.944900" "C" "11.692900" "D" "8.346500" "E" "4.015700" "F" "2.992100")
  (setq ent (entlast))
  (if ent (vl-cmdf "_.move" ent "" '(0 0 0) (list xOffset 0 0)))
  (setq xOffset (+ xOffset 23.35))

  ;; Talla ND 12.0" (OD=12.75")
  (testacpscript "UBOLT_STANDARD" "OD" "12.750000" "A" "0.875000" "B" "12.952800" "C" "13.818900" "D" "9.527600" "E" "4.252000" "F" "3.149600")
  (setq ent (entlast))
  (if ent (vl-cmdf "_.move" ent "" '(0 0 0) (list xOffset 0 0)))
  (setq xOffset (+ xOffset 26.95))

  ;; Talla ND 14.0" (OD=14.0")
  (testacpscript "UBOLT_STANDARD" "OD" "14.000000" "A" "0.875000" "B" "14.252000" "C" "15.118100" "D" "10.236200" "E" "4.252000" "F" "3.228300")
  (setq ent (entlast))
  (if ent (vl-cmdf "_.move" ent "" '(0 0 0) (list xOffset 0 0)))
  (setq xOffset (+ xOffset 29.2))

  ;; Talla ND 16.0" (OD=16.0")
  (testacpscript "UBOLT_STANDARD" "OD" "16.000000" "A" "0.875000" "B" "16.220500" "C" "17.086600" "D" "11.220500" "E" "4.252000" "F" "3.228300")
  (setq ent (entlast))
  (if ent (vl-cmdf "_.move" ent "" '(0 0 0) (list xOffset 0 0)))
  (setq xOffset (+ xOffset 32.8))

  ;; Talla ND 18.0" (OD=18.0")
  (testacpscript "UBOLT_STANDARD" "OD" "18.000000" "A" "1.000000" "B" "18.267700" "C" "19.252000" "D" "12.480300" "E" "4.724400" "F" "3.425200")
  (setq ent (entlast))
  (if ent (vl-cmdf "_.move" ent "" '(0 0 0) (list xOffset 0 0)))
  (setq xOffset (+ xOffset 36.4))

  ;; Talla ND 20.0" (OD=20.0")
  (testacpscript "UBOLT_STANDARD" "OD" "20.000000" "A" "1.000000" "B" "20.315000" "C" "21.299200" "D" "13.622000" "E" "4.724400" "F" "3.622000")
  (setq ent (entlast))
  (if ent (vl-cmdf "_.move" ent "" '(0 0 0) (list xOffset 0 0)))
  (setq xOffset (+ xOffset 40.0))

  ;; Talla ND 22.0" (OD=22.0")
  (testacpscript "UBOLT_STANDARD" "OD" "22.000000" "A" "1.000000" "B" "22.322800" "C" "23.307100" "D" "15.000000" "E" "4.724400" "F" "3.622000")
  (setq ent (entlast))
  (if ent (vl-cmdf "_.move" ent "" '(0 0 0) (list xOffset 0 0)))
  (setq xOffset (+ xOffset 43.6))

  ;; Talla ND 24.0" (OD=24.0")
  (testacpscript "UBOLT_STANDARD" "OD" "24.000000" "A" "1.000000" "B" "24.330700" "C" "25.315000" "D" "15.551200" "E" "4.724400" "F" "3.543300")
  (setq ent (entlast))
  (if ent (vl-cmdf "_.move" ent "" '(0 0 0) (list xOffset 0 0)))
  (setq xOffset (+ xOffset 47.2))

  ;; Talla ND 26.0" (OD=26.0")
  (testacpscript "UBOLT_STANDARD" "OD" "26.000000" "A" "1.000000" "B" "26.378000" "C" "27.362200" "D" "16.535400" "E" "4.724400" "F" "3.543300")
  (setq ent (entlast))
  (if ent (vl-cmdf "_.move" ent "" '(0 0 0) (list xOffset 0 0)))
  (setq xOffset (+ xOffset 50.8))

  ;; Talla ND 28.0" (OD=28.0")
  (testacpscript "UBOLT_STANDARD" "OD" "28.000000" "A" "1.000000" "B" "28.346500" "C" "29.330700" "D" "17.519700" "E" "4.724400" "F" "3.503900")
  (setq ent (entlast))
  (if ent (vl-cmdf "_.move" ent "" '(0 0 0) (list xOffset 0 0)))
  (setq xOffset (+ xOffset 54.4))

  ;; Talla ND 30.0" (OD=30.0")
  (testacpscript "UBOLT_STANDARD" "OD" "30.000000" "A" "1.000000" "B" "30.472400" "C" "31.456700" "D" "18.503900" "E" "4.724400" "F" "3.503900")
  (setq ent (entlast))
  (if ent (vl-cmdf "_.move" ent "" '(0 0 0) (list xOffset 0 0)))
  (setq xOffset (+ xOffset 58.0))

  ;; Talla ND 32.0" (OD=32.0")
  (testacpscript "UBOLT_STANDARD" "OD" "32.000000" "A" "1.000000" "B" "32.480300" "C" "33.464600" "D" "19.527600" "E" "4.724400" "F" "3.543300")
  (setq ent (entlast))
  (if ent (vl-cmdf "_.move" ent "" '(0 0 0) (list xOffset 0 0)))
  (setq xOffset (+ xOffset 61.6))

  ;; Talla ND 34.0" (OD=34.0")
  (testacpscript "UBOLT_STANDARD" "OD" "34.000000" "A" "1.000000" "B" "34.527600" "C" "35.511800" "D" "20.590600" "E" "4.724400" "F" "3.582700")
  (setq ent (entlast))
  (if ent (vl-cmdf "_.move" ent "" '(0 0 0) (list xOffset 0 0)))
  (setq xOffset (+ xOffset 65.2))

  ;; Talla ND 36.0" (OD=36.0")
  (testacpscript "UBOLT_STANDARD" "OD" "36.000000" "A" "1.000000" "B" "36.496100" "C" "37.480300" "D" "21.574800" "E" "4.724400" "F" "3.582700")
  (setq ent (entlast))
  (if ent (vl-cmdf "_.move" ent "" '(0 0 0) (list xOffset 0 0)))
  (setq xOffset (+ xOffset 68.8))

  (princ "\n[+] Configurando cámara y vista isométrica...")
  (command "_.zoom" "_e")
  (command "_.vscurrent" "_c")
  (command "_.-view" "_swiso")
  (command "_.zoom" "_e")
  (princ "\n[OK] 29 abrazaderas UBOLT_STANDARD instanciadas exitosamente!\n")
  (princ)
)

(c:TESTALLSIZES)
